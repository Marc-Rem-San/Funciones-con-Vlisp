;Lista de datos de definición arrojada por "entget"
(defun c:entget ()
  (while (not (setq ss_object (ssget "_:S+."))))
  (setq list_entget (entget (ssname ss_object 0)))
  (princ "\t\t\tLista de datos de definición arrojada por \"entget\": ") (terpri)
  (setq counter 0)  
  (repeat (length list_entget)
    (princ "\t\t\t\t\t\t\t\t\t\t\t") (princ (nth counter list_entget)) (terpri) 
    (setq counter (1+ counter))
  ) 
  (princ "\t\t\tNúmero de datos: ") (princ (length list_entget)) (terpri) (textpage)
  (progn
    (setq file_answer_r (open "c:\\Lisp_MERS\\Comandos_MERS\\mostrar lista de datos en pantalla de texto\\answer.txt" "r"))
    (setq answer_0 (read-line file_answer_r))
    (close file_answer_r)
  )
  (initget "Sí No")
  (while
    (= (if (not (setq answer (getkword (strcat "\nMostrar lista de definición especificando un código de entidad  [Sí/No] <" answer_0 ">: "))))
	 (setq answer answer_0)
	 (setq answer answer)
       )
       "Sí"
    )    
    (progn
      (terpri)
      (princ "---------------------------------------------------------------------------------------") (terpri)  
      ;Lista de datos de un nombre de entidad asociado al código aportado
      (while
	(progn
	  (initget 1)
	  (if (setq assoc_code (assoc (getint "\nEspecifique código de entidad: ") list_entget))
	    (/= (type (setq ename_code (cdr assoc_code))) 'ename)
	    (not nil)
	  )
	)
	(prompt "ADVERTENCIA: el código especificado debe corresponder a una entidad") (terpri) (textpage)
      )
      (setq list_entget_code (entget ename_code))      
      (princ "\t\t\tLista de datos de \"") (princ ename_code ) (princ "\" arrojada por \"entget\": ") (terpri)
      (setq counter 0)
      (repeat (length list_entget_code)
	(princ "\t\t\t\t\t\t\t\t\t\t\t") (princ (nth counter list_entget_code)) (terpri)
	(setq counter (1+ counter))
      )
      (princ "\t\t\tNúmero de datos: ") (princ (length list_entget_code)) (terpri) (textpage)
      (progn
	(setq file_answer_w (open "c:\\Lisp_MERS\\Comandos_MERS\\mostrar lista de datos en pantalla de texto\\answer.txt" "w"))
	(write-line answer file_answer_w)
	(close file_answer_w)
      )
      (progn
	(setq file_answer_r (open "c:\\Lisp_MERS\\Comandos_MERS\\mostrar lista de datos en pantalla de texto\\answer.txt" "r"))
	(setq answer_0 (read-line file_answer_r))
	(close file_answer_r)
      )
      (initget "Sí No")
    )
  )
  (progn
    (setq file_answer_w (open "c:\\Lisp_MERS\\Comandos_MERS\\mostrar lista de datos en pantalla de texto\\answer.txt" "w"))
    (write-line answer file_answer_w)
    (close file_answer_w)
  )
  (princ)
)
(prompt "\n\t\tComando \"entget\" cargado") (textpage)

;Lista de datos arrojada por "nentsel"
(defun c:nentsel ()
  (while (not (setq list_nentsel (nentsel)))) (terpri)
  (princ "\t\t\tLista de datos arrojada por \"nentsel\": ") (terpri)
  (setq counter 0)
  (repeat (length list_nentsel)
    (princ "\t\t\t\t\t\t\t\t\t\t\t") (princ (nth counter list_nentsel)) (terpri) 
    (setq counter (1+ counter))
  )
  (princ "\t\t\tNúmero de datos: ") (princ (length list_nentsel)) (terpri)
  (setq list_entget (entget (car list_nentsel)))
  (princ "---------------------------------------------------------------------------------------") (terpri)
  (princ "\t\t\tLista de datos de definición de \"") (princ (car list_nentsel)) (princ "\" arrojada por \"entget\": ")  (terpri) (terpri)
  (setq counter 0)
  (repeat (length list_entget)
    (princ "\t\t\t\t\t\t\t\t\t\t\t") (princ (nth counter list_entget)) (terpri) 
    (setq counter (1+ counter))
  ) 
  (princ "\t\t\tNúmero de datos: ") (princ (length list_entget)) (terpri) (textpage)
  (princ)
)
(prompt "\n\t\tComando \"nentsel\" cargado") (textpage)

;Lista de datos de definición arrojada por "entget" para un elemento que pertenece a una tabla de símbolos
(defun c:entget_elemento_tabla ()
  (progn
    (setq file_r (open "c:\\Lisp_MERS\\Comandos_MERS\\mostrar lista de datos en pantalla de texto\\datos_get.txt" "r"))
    (setq symbol_table_name_0 (read-line file_r))
    (setq symbol_name_0 (read-line file_r))
    (close file_r)
  )
  (initget "Appid Block Dimstyle Layer lType Style Ucs View vPort")
  (setq symbol_table_name (getkword (strcat "Especificar el tipo de tabla [Appid/Block/Dimstyle/Layer/lType/Style/Ucs/View/vPort] <" symbol_table_name_0 ">: ")))
  (if (= symbol_table_name nil) (setq symbol_table_name symbol_table_name_0)) 
  (setq symbol_name (getstring t (strcat "Ingresar uno de los nombres de los elementos que conforman la tabla \"" symbol_table_name "\" <" symbol_name_0 ">: ")))
  (if (or (= symbol_name nil) (= symbol_name "")) (setq symbol_name symbol_name_0))
  (progn
    (setq file_w (open "c:\\Lisp_MERS\\Comandos_MERS\\mostrar lista de datos en pantalla de texto\\datos_get.txt" "w"))
    (write-line symbol_table_name file_w)
    (write-line symbol_name file_w)
    (close file_w)
  )
  (if (tblobjname symbol_table_name symbol_name)
    (progn
      (setq list_symbol_name (entget (tblobjname symbol_table_name symbol_name))) (terpri)
      (princ "\t\t\tLista de datos de definición arrojada por \"entget\"") (terpri)
      (princ (strcat "\t\t\tdel elemento \"" symbol_name "\"")) (terpri)
      (princ (strcat "\t\t\tperteneciente a la tabla \"" symbol_table_name "\": ")) (terpri)
      (setq counter 0)
      (repeat (length list_symbol_name)
	(princ "\t\t\t\t\t\t\t\t\t\t\t") (princ (nth counter list_symbol_name)) (terpri)
	(setq counter (1+ counter))
      )
      (princ "\t\t\tNúmero de datos: ") (princ (length list_symbol_name)) (terpri)
    )
    (princ (strcat "\n\t\t\ADVERTENCIA: La tabla de símbolos \"" symbol_table_name "\" \n\t\tno contiene ningún elemento de nombre \"" symbol_name "\" "))
  )
  (textpage)
  (princ)  
)
(prompt "\n\t\tComando \"entget_elemento_tabla\" cargado") (textpage)
;nueva linea
